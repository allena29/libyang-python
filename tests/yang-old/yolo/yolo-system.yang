module yolo-system {
  yang-version 1.1;
  namespace "urn:yang:yolo:system";
  prefix sys;

  import omg-extensions { prefix ext; }
  import wtf-types { prefix types; }

  description
    "YOLO.";

  revision 1999-04-01 {
    description
      "Version update.";
    reference "RFC 2549 - IP over Avian Carriers with Quality of Service.";
    ext:human-name "2549";
  }

  revision 1990-04-01 {
    description
      "Initial version.";
    reference "RFC 1149 - A Standard for the Transmission of IP Datagrams on Avian Carriers.";
    ext:human-name "1149";
  }

  feature turbo-boost {
    description
      "Goes faster.";
  }

  feature networking {
    description
      "Supports networking.";
  }

  grouping tree {
    leaf hostname {
      description
        "The hostname.";
      type types:host;
    }

    leaf deprecated-leaf {
      description
        "A deprecated leaf.";
      type string;
    }

    leaf obsolete-leaf {
      description
        "An obsolete leaf.";
      type string;
    }

    container mode {
      description "A choice/case for config options which drive mutually exclusive options.";
      choice mode-choice {
        case case1 {
          leaf auto-discover {
            type enumeration {
              enum magic;
              enum wish;
              enum luck;
            }
            mandatory true;
          }
        }
        case case2 {
          leaf-list rules {
            type string;
          }
        }
      }
    }
    
    list url {
      description
        "An URL.";
      key "proto host";
      leaf proto {
        type types:protocol;
      }
      leaf host {
        type string;
      }
      leaf port {
        type uint16;
      }
      leaf path {
        type string;
      }
    }

    leaf number {
      description
        "A number.";
      type types:number;
    }

    leaf speed {
      description
        "The speed.";
      if-feature turbo-boost;
      type uint64;
    }

    leaf isolation-level {
      description
        "The level of isolation.";
      if-feature "turbo-boost or networking";
      type uint32;
    }
  }

  container conf {
    description
      "Configuration.";
    uses tree;
  }

  container state {
    description
      "State.";
    config false;
    uses tree;
  }

  rpc chmod {
    description
      "Change permissions on path.";
    ext:require-admin;
    input {
      leaf path {
        type string;
      }
      leaf perms {
        type types:permissions;
      }
    }
  }

  rpc format-disk {
    description
      "Format disk.";
    ext:require-admin;
    input {
      leaf disk {
        ext:human-name "Disk";
        type types:str;
      }
    }
    output {
      leaf duration {
        type uint32;
      }
    }
  }
}
